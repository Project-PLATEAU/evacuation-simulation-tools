FME workspace Converter_Flood_Meshes_to_3DTiles.fmw
Title: 浸水面作成

Parameters:
- 入力ファイル = data\high_tide\BP001_SHAPE\BP001_00010m.SHP
- 出力パス = out
- 平面直角座標系 = JGD2K-02
- 最大面数 = 10000   # Maximum Number of Triangle Faces per Tile
- LOG_FILE = $(FME_MF_DIR_USERTYPED)log\log_high_tide_BP001_00010m.txt   # Log File

Readers:
- SHAPEFILE_1: SHAPEFILE from $(入力ファイル)

Writers:
- CESIUM3DTILES_1: CESIUM3DTILES to $(出力パス)
- CESIUM3DTILES_2: CESIUM3DTILES to $(出力パス)
- CESIUM3DTILES_3: CESIUM3DTILES to $(出力パス)

Note: メッシュの融合（マルチポリゴン化） / ※融合により直線になるような座標値でも / 元のメッシュごとに区切られている模様
Note: 緯度経度でメッシュ中心点を作成した後に、平面直角座標系に変更 / （平面直角座標系でCenterPointExtractorを実施すると位置が少し歪むと考えられる）
Note: 外周について垂直の側面を作成するために外周頂点の座標を算出（隣り合うメッシュの高さが違う頂点は、平均の高さをセット）
Note: 上部表面（浸水位面）をTIN（ティン、triangulated irregular network）で構築（メッシュのままだと高さ違いによる隙間ができるため） / データサイズの圧縮のため、同一高さ（丸めて同一高さを増やす）の水平面の融合し、面の数を減らす
Note: 楕円体高に変換する前にディゾルブ（融合）を実施すると、楕円体高に変換した際に頂点の高さにずれが生じて平面としての整合性が取れないというエラーが発生することがあったため、 / 楕円体高にしてから同一水位面をディゾルブする（ディゾルブはサーフェスではできないのでポリゴン化）
Note: 上部表面（浸水位面）のみでは近づいて見た場合にリアルさが失われるため、側面（垂直面）も作成
Dissolver_全メッシュ
    ACCUM_INPUT_ATTRS = Drop Incoming Attributes
    CLEANING_TOLERANCE = Automatic
    CONNECT_Z_MODE = Ignore
    DEAGGREGATE_INPUT = Yes
    AREA -> VertexExtractor_外周頂点
    AREA -> Junction_3
    AREA -> Chopper_外周頂点

Bookmark: 入力
BP001_00120m (reader SHAPEFILE_1)
    attributes: MESH number(13,0), 標高 float, 浸水深 float, 浸水深ﾗﾝｸ short, 流速 float, 流速ﾗﾝｸ short
    -> CoordinateRounder_in
Note: 緯度経度を小数部8桁に丸める / （1mmレベル）
CoordinateRounder_in
    XPREC = 8
    YPREC = 8
    ROUNDED -> AttributeCreator_高さ
Note: ・0m地帯対応（考慮） / ・高さ丸め対応（上部（水位）と下部（地盤高）が同値になることを防ぐ ⇒ 最低水位：10cm）
Note: 高さを設定（上部＆下部）
AttributeCreator_高さ
    ATTR_TABLE:
      SET_TO height_upper = @real32(@Value(標高)+@max(@Value(浸水深), 0.1))
      SET_TO height_lower = @Evaluate(@Value(標高))
    -> CenterPointExtractor_メッシュ中心
    -> Reprojector_平面直角へ_1
Note: 平面直角座標系に変更
Reprojector_平面直角へ_1
    DEST = $(平面直角座標系)
    INTERPOLATION_TYPE_NAME = Nearest Neighbor
    RASTER_CELL_SIZE = Preserve Cells
    RASTER_TOLERANCE = 0.0
    REPROJECTED -> Dissolver_全メッシュ
    REPROJECTED -> SpatialFilter [Candidate]

Bookmark: メッシュ中心点を作成（XYZ）
Note: メッシュ中心座標（XY）を取得
CenterPointExtractor_メッシュ中心
    CENTX = _inside_x
    CENTY = _inside_y
    CENTZ = _inside_z
    EXTRACTIONMODE = CENTER
    -> VertexCreator_メッシュ中心点
Note: メッシュ中心点を作成（XYZ）
VertexCreator_メッシュ中心点
    MEASURE_TYPE = Continuous
    MODE_NAME = Replace with Point
    XVAL = @Value(_inside_x)
    YVAL = @Value(_inside_y)
    ZVAL = @real32(@Value(height_upper))
    -> Reprojector_平面直角へ_2
Note: 平面直角座標系に変更
Reprojector_平面直角へ_2
    DEST = $(平面直角座標系)
    INTERPOLATION_TYPE_NAME = Nearest Neighbor
    RASTER_CELL_SIZE = Preserve Cells
    RASTER_TOLERANCE = 0.0
    REPROJECTED -> CoordinateRounder_上部表面

Bookmark: 外周頂点を作成（XYZ）
Note: 外周のラインを作成
Chopper_外周頂点
    DEAGGREGATE_INPUT = Deaggregate
    MAX_VERTICES = 2
    MODE = By Vertex
    REMNANT_ATTR = _remnant
    CHOPPED -> Aggregator_外周ライン
Note: 外周のラインを集約
Aggregator_外周ライン
    ACCUM_ATTRS_NAME = Drop Incoming Attributes
    AGGREGATE_TYPE = Homogeneous Collection (If Possible)
    MODE = Geometry - Assemble One Level
    SEP = ,
    AGGREGATE -> SpatialFilter [Filter]
Note: 外周のメッシュのみ抽出
SpatialFilter
    AGGREGATE_HANDLING = Yes
    BASE_TYPE = Single Filter
    CURVE_BOUNDARY_RULE_PARAM = Default Rule
    PASS_CRITERIA = Pass Against One Filter
    PREDATTR = _predicate
    PREDICATES = TOUCHES
    USE_BOUNDING_BOX = No
    PASSED -> VertexExtractor_各メッシュ
Note: 各メッシュの頂点を抽出
VertexExtractor_各メッシュ
    DEFAULT_Z_VALUE = 0
    Point -> AttributeRangeFilter
Note: 各メッシュの頂点の5番目 / （最初の位置に戻って来た頂点）を削除
AttributeRangeFilter
    IN_ATTR = _vertex_number
    LUT = 0,3,0 .. 3
    0 .. 3 -> NeighborFinder [CANDIDATE]
Note: 外周の頂点を抽出し、 / 高さゼロをセット
VertexExtractor_外周頂点
    DEFAULT_Z_VALUE = 0
    Point -> NeighborFinder [BASE]
Note: 近接するメッシュ頂点を探索し、 / 属性情報をリストに追加 / （最大で3点ヒット）
NeighborFinder
    CANDIDATES_FIRST = No
    CLOSE_LIST_ATTRS_TO_INCLUDE = height_lower height_upper
    CLOSE_LIST_ATTRS_TO_INCLUDE_MODE = Selected Attributes
    CLOSE_LIST_NAME = list
    INSERT_VERTEX = No
    K = 3
    MAX = 1
    MEASURES_FROM_CANDIDATE = No
    MEASURE_TYPE = Continuous
    MODE = Bases and Candidates
    TREAT_POLYGON_AS = Areas
    MATCHED -> ListStatisticsCalculator_上部
    MATCHED -> ListStatisticsCalculator_下部
Note: 隣接するメッシュの上部の / 平均高さを算出（最大で3メッシュ）
ListStatisticsCalculator_上部
    LIST_ATTR = list{}.height_upper
    PREFIX = stats_hu_
    -> VertexCreator_外周上部_頂点
Note: 外周上部の頂点を作成（XYZ）
VertexCreator_外周上部_頂点
    MEASURE_TYPE = Continuous
    MODE_NAME = Replace with Point
    XVAL = @Value(_x)
    YVAL = @Value(_y)
    ZVAL = @Value(stats_hu_mean)
    -> CoordinateRounder_上部表面
Note: 隣接するメッシュの下部の / 平均高さを算出（最大で3メッシュ）
ListStatisticsCalculator_下部
    LIST_ATTR = list{}.height_lower
    PREFIX = stats_hl_
    -> VertexCreator_外周下部_頂点
Note: 外周下部の頂点を作成（XYZ）
VertexCreator_外周下部_頂点
    MEASURE_TYPE = Continuous
    MODE_NAME = Replace with Point
    XVAL = @Value(_x)
    YVAL = @Value(_y)
    ZVAL = @Value(stats_hl_mean)
    -> CoordinateRounder_下部

Bookmark: 上部表面のTINサーフェスを作成
Note: 高さを10cm単位で丸める
CoordinateRounder_上部表面
    ZPREC = 1
    ROUNDED -> TINGenerator_上部表面 [POINTS/LINES]
Note: Surface Toleranceの値を0より大きく / することで頂点を間引くことができる
TINGenerator_上部表面
    TOLERANCE = 0
    TRIANGLES -> Clipper_上部表面 [CANDIDATE]
Note: TINサーフェスをクリップ（バージョンアップで挙動が変わった） / https://community.safe.com/s/article/how-to-clip-tin-surfaces
Note: ポリゴン
Clipper_上部表面
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Junction
    INSIDE -> CsmapReprojector_1

Bookmark: 側面下部の高さを取得
Note: 高さを10cm単位で丸める
CoordinateRounder_下部
    ZPREC = 1
    ROUNDED -> TINGenerator_下部 [POINTS/LINES]
TINGenerator_下部
    TOLERANCE = 0
    TRIANGLES -> Clipper_下部 [CANDIDATE]
Junction_3
    -> Clipper_上部表面 [CLIPPER]
    -> Clipper_下部 [CLIPPER]
Clipper_下部
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> SurfaceDraper_下部 [POINTS/LINES]

Bookmark: 側面を作成
Junction
    -> SurfaceDraper_上部 [POINTS/LINES]
    -> 2DForcer
Note: 平面化
2DForcer
    2D -> Dissolver_側面立ち上げライン用
Note: 融合
Dissolver_側面立ち上げライン用
    ACCUM_INPUT_ATTRS = Drop Incoming Attributes
    CLEANING_TOLERANCE = Automatic
    CONNECT_Z_MODE = Ignore
    DEAGGREGATE_INPUT = Yes
    AREA -> Chopper_側面用ライン
Note: 外周のラインを作成
Chopper_側面用ライン
    DEAGGREGATE_INPUT = Deaggregate
    MAX_VERTICES = 2
    MODE = By Vertex
    REMNANT_ATTR = _remnant
    CHOPPED -> Counter_側面
Note: SurfaceOnSurfaceOverlayer / で利用
Counter_側面
    CNT_ATTR = _count_side_surface
    DOMAIN = counter
    SCOPE = Global
    START = 0
    -> Junction_4
Junction_4
    -> SurfaceDraper_上部 [DRAPE_FEATURES]
    -> SurfaceDraper_下部 [DRAPE_FEATURES]
Note: 側面生成用ラインを作成 / （外周のラインの各頂点に高さを適用）
SurfaceDraper_上部
    ADDZ_TYPE = Replace Z
    DRAPE_TYPE = VERTEX
    INTERPOLATION_TYPE = AUTO
    TOLERANCE = 0
    DRAPED_FEATURES -> Extruder_側面_負方向
Note: 側面を作成 / 100m押し下げ（負方向）
Extruder_側面_負方向
    DIRECTION = Vertical
    DISTANCE = -100
    EXTRUDED -> SurfaceOnSurfaceOverlayer [SURFACE]
SurfaceDraper_下部
    ADDZ_TYPE = Replace Z
    DRAPE_TYPE = VERTEX
    INTERPOLATION_TYPE = AUTO
    TOLERANCE = 0
    DRAPED_FEATURES -> Extruder_側面_正方向
Note: 側面を作成100m押し上げ
Extruder_側面_正方向
    DIRECTION = Vertical
    DISTANCE = 100
    EXTRUDED -> SurfaceOnSurfaceOverlayer [SURFACE]
Note: グループ（CounterでIDを振る）ごとに / 共通のサーフェス部分を作成
SurfaceOnSurfaceOverlayer
    ACCUM_ATTRS_NAME = Use Attributes From One Feature
    DEAGGREGATE_INPUT = No
    ENABLE_TOLERANCE = Yes
    GROUP_BY = _count_side_surface
    NORMAL_TOLERANCE = 1
    OFFSET_TOLERANCE = 1
    OVC_ATTR = _overlaps
    SURFACE -> Tester_共通サーフェスの判定
Note: サーフェス
Note: 共通部分のみ抽出
Tester_共通サーフェスの判定
    BOOL_OP = OR
    TEST_CLAUSE = TEST @Value(_overlaps) = 2
    TEST_MODE = TEST
    PASSED -> CsmapReprojector_2

Bookmark: 上部表面と側面を集約
Note: WGS84（EPSG：4979）に変換 / 楕円体高に変換（ジオイド高補正）
CsmapReprojector_1
    DEST = EPSG:4979
    GEOID_HEIGHT_GRID = $(FME_HOME)Reproject\GeoidHeightGrids\World\Egm96-Wgs84.gdc
    INTERPOLATION_TYPE_NAME = Nearest Neighbor
    RASTER_CELL_SIZE = Preserve Cells
    RASTER_TOLERANCE = 0.0
    VERTICAL_HANDLING = Orthometric height -> Geocentric or ellipsoid height
    REPROJECTED -> CoordinateRounder_WGS84変換後_1
Note: 緯度経度は小数部8桁（1mmレベル）、 / 高さは小数部2桁（1cm単位）で丸める
CoordinateRounder_WGS84変換後_1
    XPREC = 8
    YPREC = 8
    ZPREC = 2
    ROUNDED -> SlopeCalculator
Note: 上部表面：フラグ=1
ExpressionEvaluator_上部表面フラグ
    ACTION = Create New Attribute
    EXPRESSION = 1
    VAL_ATTR = _objFlag
    -> AttributeKeeper_面タイプのみ
Note: WGS84（EPSG：4979）に変換 / 楕円体高に変換（ジオイド高補正）
CsmapReprojector_2
    DEST = EPSG:4979
    GEOID_HEIGHT_GRID = $(FME_HOME)Reproject\GeoidHeightGrids\World\Egm96-Wgs84.gdc
    INTERPOLATION_TYPE_NAME = Nearest Neighbor
    RASTER_CELL_SIZE = Preserve Cells
    RASTER_TOLERANCE = 0.0
    VERTICAL_HANDLING = Orthometric height -> Geocentric or ellipsoid height
    REPROJECTED -> CoordinateRounder_WGS84変換後_2
Note: 緯度経度は小数部8桁（1mmレベル）、 / 高さは小数部2桁（1cm単位）で丸める
CoordinateRounder_WGS84変換後_2
    XPREC = 8
    YPREC = 8
    ZPREC = 2
    ROUNDED -> SurfaceDissolver
Note: 側面：フラグ=2
ExpressionEvaluator_側面フラグ
    ACTION = Create New Attribute
    EXPRESSION = 2
    VAL_ATTR = _objFlag
    -> AttributeKeeper_面タイプのみ
Note: 面の種類（_objFlag）のみ残す
AttributeKeeper_面タイプのみ
    CREATE_BULK_MODE_FEATURES = NO
    KEEP_ATTRS = _objFlag
    -> FilenamePartExtractor
Note: 入力ァイルのパス・名前等の文字列を付与
FilenamePartExtractor
    DIRNAME_ATTR = _dirname
    DIRPATH_ATTR = _dirpath
    EXTENSION_ATTR = _extension
    FULLNAME_ATTR = _filename
    ROOTNAME_ATTR = _rootname
    SRC_ATTR = $(入力ファイル)
    -> Tester_表面の種類

Bookmark: 同一水位を集約
Note: 楕円体高にしてからの傾きを再計算
SlopeCalculator
    -> Tester_水平面の判定
Note: 水平面かどうかを判定
Tester_水平面の判定
    BOOL_OP = OR
    TEST_CLAUSE = TEST @Value(_slope) = 0
    TEST_MODE = TEST
    PASSED -> CoordinateExtractor
    FAILED -> FaceReplacer_上部表面
Note: 一番目の頂点の座標を取得
CoordinateExtractor
    IND = 0
    MODE = Specify Coordinate
    X_ATTR = _x
    Y_ATTR = _y
    Z_ATTR = _z
    -> ExpressionEvaluator_水平面融合用
Note: round(高さm×100)でIDを振る
ExpressionEvaluator_水平面融合用
    ACTION = Create New Attribute
    EXPRESSION = @round(@Value(_z)*100, 2)
    VAL_ATTR = _top_group_ID
    -> Dissolver_同一高さ
Note: 同一高さの表面を融合
Dissolver_同一高さ
    ACCUM_INPUT_ATTRS = Drop Incoming Attributes
    CLEANING_TOLERANCE = Automatic
    CONNECT_Z_MODE = Ignore
    DEAGGREGATE_INPUT = Yes
    GROUP_BY = _top_group_ID
    AREA -> Generalizer_水平面
Note: 余分な頂点を削除
Generalizer_水平面
    ALG_TEXT = Douglas (Generalize)
    CLEANING_TOLERANCE = Automatic
    PRESERVE = Yes
    PRESERVE_PATHS = No
    TOLERANCE = 0.0000001
    -> FaceReplacer_上部表面
Note: サーフェス化
FaceReplacer_上部表面
    ANGULAR_TOLERANCE_CHOICE = Automatic
    THICKNESS_TOLERANCE_CHOICE = Automatic
    -> ExpressionEvaluator_上部表面フラグ

Bookmark: 側面の集約および余分な頂点の削除
Note: サーフェスを集約
SurfaceDissolver
    ACCUM_INPUT_ATTRS = Use Attributes From One Feature
    DEAGGREGATE_INPUT = Yes
    MATCHING_APPS = No
    NORMAL_TOLERANCE = 0.01
    OFFSET_TOLERANCE = 0.0000001
    SEPARATE_SURFACES = No
    SURFACE -> GeometryCoercer_側面
Note: ポリゴン化
GeometryCoercer_側面
    GQUERY:
      for $geom in //geometry
      where $geom/count(parent::geometry) = 0
      return number($geom/@fme_id)
    KIND = fme_polygon
    COERCED -> PythonCaller_余分な頂点を削除
Note: GeneralizerやZigzagRemover、SpikeRemover等は高さに関する処理ができないため、 / 頂点の高さを両隣と比較して同値の場合、当該頂点を削除するトランスフォーマーを自作
PythonCaller_余分な頂点を削除
    PYTHONSOURCE:
      import fme
      import fmeobjects


      class FeatureProcessor(object):
          """Template Class Interface:
          When using this class, make sure its name is set as the value of the 'Class
          to Process Features' transformer parameter.
          """

          def __init__(self):
              """Base constructor for class members."""
              self.polygons = []

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              geomType = feature.getGeometryType()
              if geomType == fmeobjects.FME_GEOM_POLYGON:
                  self.polygons.append(feature)

          def close(self):
              """This method is called once all the FME Features have been processed
              from input().
              """
              # 参考
              # https://docs.safe.com/fme/html/fmepython/api/fmeobjects/_feature/fmeobjects.FMEFeature.html
              for polygon in self.polygons:
                  vertices = polygon.getAllCoordinates()
                  pop_index_list = []
                  for num in range(1, len(vertices)-1, 1):
                      z_diff1 = vertices[num][2] - vertices[num-1][2]
                      z_diff2 = vertices[num][2] - vertices[num+1][2]
                      if z_diff1==0 and z_diff2==0:
                          pop_index_list.append(num)
                  for i in sorted(pop_index_list, reverse=True):
                      vertices.pop(i)
                  boundary = fmeobjects.FMELine(vertices)
                  polygon.setGeometry(fmeobjects.FMEPolygon(boundary))
                  self.pyoutput(polygon)

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> FaceReplacer_側面
Note: サーフェスに戻す / 非平面の原因となる誤差を無視
FaceReplacer_側面
    ANGULAR_TOLERANCE_CHOICE = Ignore
    THICKNESS_TOLERANCE_CHOICE = Ignore
    -> ExpressionEvaluator_側面フラグ

Bookmark: サーフェスの配色設定
Note: 上部表面と側面に分ける
Tester_表面の種類
    BOOL_OP = OR
    TEST_CLAUSE = TEST @Value(_objFlag) = 1
    TEST_MODE = TEST
    PASSED -> AppearanceSetter_上部表面 [GEOMETRY]
    FAILED -> AppearanceSetter_側面 [GEOMETRY]
Note: オブジェクトの色をセット / フロントは上面
AppearanceSetter_上部表面
    ALPHA = 0.8
    AMBIENT_COLOR = 0,0,0
    DEF_STORAGE = Create New Definitions
    DIFFUSE_COLOR = 0,0,0.1
    EMISSIVE_COLOR = 0,0,0.2
    GQUERY:
      for $geom in //geometry
      where $geom/count(parent::geometry) = 0
      return number($geom/@fme_id)
    SET_ON_SIDE = Front Side
    SHININESS = 0.5
    SPECULAR_COLOR = 0,0,0.15
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> BP001_00120m (writer CESIUM3DTILES_2)
    -> Junction_5
Note: オブジェクトの色をセット / （不透明度低め）
AppearanceSetter_側面
    ALPHA = 0.4
    AMBIENT_COLOR = 0,0,0
    DEF_STORAGE = Create New Definitions
    DIFFUSE_COLOR = 0,0,0.1
    EMISSIVE_COLOR = 0,0,0.2
    GQUERY:
      for $geom in //geometry
      where $geom/count(parent::geometry) = 0
      return number($geom/@fme_id)
    SET_ON_SIDE = Front and Back Sides
    SHININESS = 0.5
    SPECULAR_COLOR = 0,0,0.15
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> SurfaceSplitter
Note: 裏表の面をぞれぞれ生成
SurfaceSplitter
    FRONT -> Junction_2
    BACK -> Junction_2

Bookmark: 出力
Note: 上部表面のみ
BP001_00120m (writer CESIUM3DTILES_2)
Note: 現状では、FMEの3D Tiles Writer がサーフェスの裏面の出力に対応していないようで（3D Tiles自体は対応している）、裏側から見ると透明となってしまう。 / https://community.safe.com/s/question/0D54Q00008GoK6lSAF/cesium-3d-tiles-oneside-surface / 全てのオブジェクトに対してユーザーから見える側を表にすることは簡単ではないため、 / AppearanceSetter（もしくはGeometryColorSetter）で両面を作成後、 / 本トランスフォーマー（SurfaceSplitter）を利用し、側面の全オブジェクトを裏表ペアで生成する。 / サーフェスの数が2倍になるため、データサイズが大きくなるのは問題ではある。
Junction_2
    -> BP001_00120m (writer CESIUM3DTILES_3)
    -> Junction_5
Junction_5
    -> _rootname (writer CESIUM3DTILES_1)
Note: 上部表面＆側面
_rootname (writer CESIUM3DTILES_1)
Note: 側面のみ
BP001_00120m (writer CESIUM3DTILES_3)

FME custom transformer ListStatisticsCalculator
Calculates fundamental statistics of element values in the specified list, and adds attributes storing the calculation results to the feature.
    Only decimal numbers can be accepted as the list elements. 0 at the head of an element will be ignored. 
    If the incoming feature does not have list attribute with the specified name, or the list contains one or more non-numeric elements, then the feature will be output from the 
    <Rejected>
    port.
    Every rejected feature will have an attribute named "_liststats_error", which contains a text describing the rejected reason. 
    This transformer contains a Python script, which was tested with both Python 2.7 interpreter and 3.6 interpreter.
Parameters
    List Attribute
    :
    Specify a list name which contains numeric elements.
    Prefix of Statistics Attributes
    :
    Specify a common prefix which should be added to names of result attributes. This can be set to empty string, if unnecessary.
    Output features will have these attributes if you specify "stats_" to this parameter.
    -----
    stats_min - The minimum value in all the values. 
    stats_max - The maximum value in all the values. 
    stats_median - The middle value of all the values. 
    stats_count - The number of the elements. 
    stats_sum - The sum of all the values. 
    stats_range - The difference between the minimum and the maximum. i.e. equals to the maximum minus the minimum. 
    stats_mean - The average of all the values. 
    stats_stdev - The standard deviation (sample) of all the values. This will be empty if the number of elements is equal to 1.
    stats_stdevp - The standard deviation (population) of all the values. 
    stats_mode - The most frequent of all the values. If two or more values occur with the highest frequency, one of them will be returned randomly. 
    -----

Parameters:
- LIST_ATTR =   # " " List Attribute
- PREFIX = stats_   # TYPE:varchar(200) Prefix of Statistics Attributes

Input (input)
    -> ParameterFetcher
ParameterFetcher
    ATTR_LIST = liststatisticscalculator.list_attr {$(LIST_ATTR)}
    -> PythonCaller
PythonCaller
    NEW_ATTRIBUTES = min.liststatisticscalculator max.liststatisticscalculator median.liststatisticscalculator count.liststatisticscalculator sum.liststatisticscalculator range.liststatisticscalculator mean.liststatisticscalculator stdev.liststatisticscalculator stdevp.liststatisticscalculator mode.liststatisticscalculator liststatisticscalculator.histogram{}.count liststatisticscalculator.histogram{}.value liststatisticscalculator.flag
    PYTHONSOURCE:
      # 2018-06-14, Takashi Iijime, Updated to support Python 3.x interpreter.
      # 2016-06-24, Takashi Iijima, Added stdevp - standard deviation (population).
      # 2014-08-02, Takashi Iijima, Original Implementation

      import fmeobjects, locale, re, math

      class ListStatisticsCalculator(object):
          def __init__(self):
              import platform
              if platform.python_version_tuple()[0] == '2':
                  loc = locale.getdefaultlocale()
                  enc = loc[1] if loc else 'utf_8'
                  self.toStr = lambda s: s.encode(enc) if isinstance(s, unicode) else s
              else:
                  self.toStr = lambda s: s

          def input(self, feature):
              try:
                  listName = self.toStr(feature.getAttribute('liststatisticscalculator.list_attr'))
                  m = re.match(r'^(.+)\{\}(.*)$', listName)

                  front, index, back = m.group(1), 0, m.group(2)
                  values, total, histogram = [], 0.0, {}
                  while True:
                      v = feature.getAttribute('%s{%d}%s' % (front, index, back))
                      if v == None:
                          break
                      v = float(v)
                      values.append(v)
                      total += v
                      histogram[v] = histogram.setdefault(v, 0) + 1
                      index += 1

                  # Number of elements.
                  count = len(values)
                  if count < 1:
                      raise Exception('could not find valid element')
                  values.sort() # ascending sort

                  # Calculate median, average (mean) and standard deviation.
                  mid = count // 2
                  median = values[mid] if count % 2 else 0.5 * (values[mid - 1] + values[mid])
                  avrg = total / count
                  s = sum([(v - avrg)**2 for v in values])
                  stdev = math.sqrt(s / (count - 1)) if 1 < count else ''
                  stdevp = math.sqrt(s / count)

                  # Find mode.
                  mode, num = None, 0
                  for i, v in enumerate(sorted(histogram.keys())):
                      n = histogram[v]
                      if num < n:
                          mode, num = v, n
                      # Reserved: Set histogram elements
                      #feature.setAttribute('liststatisticscalculator.histogram{%d}.count' % i, n)
                      #feature.setAttribute('liststatisticscalculator.histogram{%d}.value' % i, v)

                  # Set statistics attributes.
                  feature.setAttribute('min.liststatisticscalculator', values[0])
                  feature.setAttribute('max.liststatisticscalculator', values[-1])
                  feature.setAttribute('median.liststatisticscalculator', median)
                  feature.setAttribute('count.liststatisticscalculator', count)
                  feature.setAttribute('sum.liststatisticscalculator', total)
                  feature.setAttribute('range.liststatisticscalculator', values[-1] - values[0])
                  feature.setAttribute('mean.liststatisticscalculator', avrg)
                  feature.setAttribute('stdev.liststatisticscalculator', stdev)
                  feature.setAttribute('stdevp.liststatisticscalculator', stdevp)
                  feature.setAttribute('mode.liststatisticscalculator', mode)

                  # Set flag.
                  feature.setAttribute('liststatisticscalculator.flag', 1)

              except Exception as ex:
                  feature.setAttribute('_liststats_error', '%s' % ex)
                  feature.setAttribute('liststatisticscalculator.flag', 0)

              self.pyoutput(feature)
    PYTHONSYMBOL = ListStatisticsCalculator
    -> Tester
Tester
    BOOL_OP = OR
    TEST_CLAUSE = TEST @Value(liststatisticscalculator.flag) = 1
    TEST_MODE = Automatic
    PASSED -> BulkAttributeRenamer
    FAILED -> BulkAttributeRemover_2
Note: Add common prefix
BulkAttributeRenamer
    ATTRCHOICE = Selected Attributes
    ATTRLIST = min.liststatisticscalculator max.liststatisticscalculator median.liststatisticscalculator count.liststatisticscalculator sum.liststatisticscalculator range.liststatisticscalculator mean.liststatisticscalculator stdev.liststatisticscalculator stdevp.liststatisticscalculator mode.liststatisticscalculator
    PATTERN_ACTION_DISP = Add String Prefix
    REPLACE_STR = $(PREFIX)
    -> BulkAttributeRenamer_2
Note: Remove extra suffix
BulkAttributeRenamer_2
    ATTRCHOICE = All Attributes
    CASE_DISP = yes
    PATTERN_ACTION_DISP = Remove Suffix String
    REPLACE_STR = .liststatisticscalculator
    -> BulkAttributeRemover
Note: Remove unnecessary attributes
BulkAttributeRemover
    ATTR_EXP = ^liststatisticscalculator
    -> Output (output)
Output (output)
BulkAttributeRemover_2
    ATTR_EXP = liststatisticscalculator
    -> AttributeExposer
Note: AttributeExposer [AttributeExposer] / Attributes To Expose: _liststats_error
AttributeExposer
    ATTR_LIST = _liststats_error
    -> <Rejected> (output)
<Rejected> (output)

FME custom transformer SlopeCalculator
This transformer calculates the slope of input polygons and surfaces.
It works by extracting the bounds of an input feature and comparing its maximum and minimum Z values.  
If the difference is 0, then the surface is deemed flat with zero slope.
If the difference is not zero, then the input feature is triangulated, and the slope of each of its triangles is calculated. The slope is presented as the average of the slopes of its triangles.
Input Ports
Input
Input features must have geometry of type polygon or surface.
Output Ports
Output
Features are output with a new attribute with the slope of source data. 
_slope: Contains the value of slope in degrees.
<Rejected>
Features will be passed through this port if they are not of type polygon (area, ellipse) or surface. The attribute fme_rejection_code will be added to each feature with value INVALID_GEOMETRY_TYPE.
Parameters 
This transformer has no parameters.
Usage Notes
For best results, make sure that input surfaces are planar.

Input (input)
    -> GeometryFilter
Counter
    CNT_ATTR = SC_count
    DOMAIN = SC_count
    SCOPE = Local
    START = 0
    -> BoundsExtractor_2
Note: Extract face bounds
BoundsExtractor_2
    XMAX = _xmax
    XMIN = _xmin
    YMAX = _ymax
    YMIN = _ymin
    ZMAX = _zmax
    ZMIN = _zmin
    -> Tester_2
Note: Determine if surface is flat or sloped
Tester_2
    BOOL_OP = OR
    TEST_CLAUSE = TEST @Value(_zmin) = @Value(_zmax)
    TEST_MODE = TEST
    PASSED -> AttributeCreator_4
    FAILED -> Triangulator
    FAILED -> FeatureMerger [REQUESTOR]
Note: Flat surfaces simply get 0 for slope
AttributeCreator_4
    ATTR_TABLE = SET_TO SLOPE = 0
    -> AttributeManager
Note: Add the calculated slope / to the original faces
FeatureMerger
    ATTR_ACCUM_MODE = Merge Supplier
    ATTR_CONFLICT_RES = Use Requestor
    IGNORE_NULLS = Yes
    JOIN_KEYS = @Value(SC_count) @Value(SC_count) AUTO
    MERGE_TYPE = Attributes Only
    PROCESS_DUPS = NO
    REJECT_NULL_MISSING_KEYS = No
    SUPPLIERS_FIRST = No
    MERGED -> AttributeManager
Note: Clean up features
AttributeManager
    ATTR_TABLE:
      REMOVE SC_count
      REMOVE _xmax
      REMOVE _xmin
      REMOVE _ymax
      REMOVE _ymin
      REMOVE _zmax
      REMOVE _zmin
      RENAME_SET_VALUE SLOPE > _slope
    -> Output (output)
Output (output)
<Rejected> (output)

Bookmark: Validate geometry
GeometryFilter
    BREAK_AGG = No
    GEOM_PORT_NAMES = Area Ellipse Surface
    AREA -> Counter
    ELLIPSE -> Counter
    SURFACE -> Counter
    <UNFILTERED> -> AttributeCreator_5
AttributeCreator_5
    ATTR_TABLE = SET_TO fme_rejection_code = INVALID_GEOMETRY_TYPE
    -> <Rejected> (output)

Bookmark: Replace faces with triangles
Triangulator
    DEAGGREGATE_INPUT = Deaggregate
    TRIANGLES -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> GeometryCoercer
GeometryCoercer
    GQUERY:
      for $geom in //geometry
      where $geom/count(parent::geometry) = 0
      return number($geom/@fme_id)
    KIND = fme_polygon
    COERCED -> CoordinateExtractor_2

Bookmark: Extract coordinates of the triangle vertices
CoordinateExtractor_2
    IND = 0
    MODE = Specify Coordinate
    X_ATTR = _x0
    Y_ATTR = _y0
    Z_ATTR = _z0
    Z_DEFAULT = -9999
    -> CoordinateExtractor_3
CoordinateExtractor_3
    IND = 1
    MODE = Specify Coordinate
    X_ATTR = _x1
    Y_ATTR = _y1
    Z_ATTR = _z1
    Z_DEFAULT = -9999
    -> CoordinateExtractor_4
CoordinateExtractor_4
    IND = 2
    MODE = Specify Coordinate
    X_ATTR = _x2
    Y_ATTR = _y2
    Z_ATTR = _z2
    Z_DEFAULT = -9999
    -> AttributeCreator

Bookmark: Calculate slopes
Note: Create two vectors that / connect the triangle's / vertices (from one vertex / to the other two)
AttributeCreator
    ATTR_TABLE:
      SET_TO _u1 = @Evaluate(@Value(_x0)-@Value(_x2))
      SET_TO _v1 = @Evaluate(@Value(_x1)-@Value(_x2))
      SET_TO _u2 = @Evaluate(@Value(_y0)-@Value(_y2))
      SET_TO _v2 = @Evaluate(@Value(_y1)-@Value(_y2))
      SET_TO _u3 = @Evaluate(@Value(_z0)-@Value(_z2))
      SET_TO _v3 = @Evaluate(@Value(_z1)-@Value(_z2))
    -> AttributeCreator_2
Note: Take a cross product of the / two vectors to find a vector / that is normal to the triangle
AttributeCreator_2
    ATTR_TABLE:
      SET_TO _nx = @Evaluate(@Value(_u2)*@Value(_v3)-@Value(_u3)*@Value(_v2))
      SET_TO _ny = @Evaluate(@Value(_u3)*@Value(_v1)-@Value(_u1)*@Value(_v3))
      SET_TO _nz = @Evaluate(@Value(_u1)*@Value(_v2)-@Value(_u2)*@Value(_v1))
    -> AttributeCreator_3
Note: Find the length of the normal's / projection on the x,y plane
AttributeCreator_3
    ATTR_TABLE = SET_TO _length = @Evaluate(@sqrt(@Value(_nx)*@Value(_nx)+@Value(_ny)*@Value(_ny)))
    -> AttributeCreator_6
Note: Find the triangle's slope: / - First find the absolute value / of its normal's slope. / - A plane's normal is perpendicular / to that plane, hence their slope / differs by 90 degrees (PI/2 radians)
AttributeCreator_6
    ATTR_TABLE = SET_TO _slope = @Evaluate(3.14159/2.0-@atan2(@abs(@Value(_nz)),@abs(@Value(_length))))
    -> AttributeCreator_7
Note: Convert from / radians to degrees
AttributeCreator_7
    ATTR_TABLE = SET_TO SLOPE = @Evaluate(@Value(_slope)*180.0/3.14159)
    -> StatisticsCalculator
Note: Find the average
StatisticsCalculator
    COMPUTE_HISTOGRAM = NO
    GROUP_BY = SC_count
    MEAN_ATTR = SLOPE
    PREPEND_ATTR_NAME_CHOICE = For multiple results only
    STATS_ATTRS = SLOPE
    SUMMARY -> FeatureMerger [SUPPLIER]
